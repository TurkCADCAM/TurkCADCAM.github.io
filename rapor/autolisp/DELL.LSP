(defun c:dell()
  (setq p1(getpoint "\nDelinecek nesne dışında bir nokta seçin:"))
  (setq p2(getpoint "\nDelinecek nesne içinde bir nokta seçin:"))
  (setq nesne(ssget "c" p1 p2))
  (setq yer(getpoint "\nMerkez noktası :"))
  (setq r(getreal "\nYariçapı girin :"))
  (setq h(getreal "\nYüksekliği Girin :"))
  (command "ucs" "origin" yer)
  (command "cylinder" "0,0,0" r h)
  (command "subtract"  nesne "" "last" "")
  (setq nh(* -1 h))
  (command "cylinder" "0,0,0" r nh)
  (command "subtract"  nesne "" "last" "")
  (command "ucs" "world" "")  
)
